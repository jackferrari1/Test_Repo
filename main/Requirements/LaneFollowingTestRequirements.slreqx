# LaneFollowingTestRequirements

## scenarioId #1: ACC_ISO_TargetDiscriminationTest (Functional)
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
## scenarioId #2: ACC_ISO_AutoRetargetTest (Functional)
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- Rationale: ISO 22178

## scenarioId #3: ACC_ISO_CurveTest (Functional)
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- Rationale: ISO 15622
  ISO 22178

## scenarioId #4: ACC_StopnGo (Functional)
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- Rationale: Real world scenario

## scenarioId #5: LFACC_DoubleCurveDecelTarget (Functional)
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- Rationale: Real world scenario

## scenarioId #6: LFACC_DoubleCurve_AutoRetarget (Functional)
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- Rationale: ~ISO 22178

## scenarioId #7: LFACC_DoubleCurveStopnGo (Functional)
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- Rationale: Real-world scenario

## scenarioId #8: LFACC_Curve_CutInOut (Functional)
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- Rationale: Real-world scenario

## scenarioId #9: LFACC_Curve _CutInOut_TooClose (Functional)
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- Rationale: Real-world Scenario
